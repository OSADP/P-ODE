-- Version: 0.2.3
-- Date: 2015-02-24
-- Developed by Leidos
-- for the FHWA Prototype Operational Data Environment
-- 
-- ASN.1 Schema validation site: http://asn1-playground.oss.com/
-- ASN.1 to XML Schema Definition (XSD) site:  http://www.obj-sys.com/webtools/asn2xsd.php
--
-- Change log:
-- 0.2.3
-- changed "speed" from mandatory to optional in PodeDataElementList
-- changed Sha256Hash from a size of 32 to a size of 64 to account for the potential lengths of messageID 

-- 0.2.2
-- added PodeProtocol data element
-- added PodeProtocol to PodeSubscriptionRequest to enable the subscriber to request the network protocol in which the Core should deliver data
-- began development on PodeArchiveData (for (2C) pode Archive Data), PodeAchriveDataRequest (for (3C) Data Archive Retrieval), and PodeArchiveDataDistribution (for (3C) Data Archive Retrieval)

-- 0.2.1
-- added msgSize to PodeLogMessage
-- renamed DataConfirmation to PodeDataConfirmation, due to P-ODE customization
-- added PodeDataDestination to PodeDataConfirmation
-- added PodeDataDestination

-- 0.2.0
-- Official change from AUTOMATIC to IMPLICIT tags
-- Added (3C) log Data to PodeDialogID as 0x00C7
-- Added PodeLogDataRequest (for (3C) Log Data Data Flow)
-- Added PodeLogDataResponse (for (3C) Log Data Data Flow)

-- 0.1.4
-- Test change from AUTOMATIC to IMPLICIT tags
-- <name> [tag] <object>
-- Example:
	-- dialogID [0]PodeDialogID
		-- <name> = dialogID
		-- [tag] = [0]
		-- <object> = PodeDialogID
-- added (1B) Log Message
-- Added (3C) Log Data
-- renamed "long" to "lon" in Position3D, due to Java conflict
-- Still need to Finalize:
--		(2C) pode Archive Data
--		(3C) Data Archive Retrieval

-- 0.1.3
-- added messageID to PodeDataDistribution
-- added PodeDataDelivery
-- added PodeLogMessage
-- added PodeLogData
-- Still need to Finalize:
--		(2C) pode Archive Data
--		(3C) Data Archive Retrieval

-- 0.1.2
-- changed PodeDataElements to PodeDataTypes
-- added weather to PodeDataTypes
-- added (1B) Data Pub Reg Data Flow definitions
-- Added (2c) Data Sub Reg Data Flow definitions
-- Added (1B) Data Delivery definitions
-- Still need to Finalize:
--		(1B) Log Message
--		(3C) Log Data
--		(2C) pode Archive Data
--		(3C) Data Archive Retrieval

-- 0.1.1:
-- added SPaT & Map data source
-- change PodeDataRecord from a sequence to a single instance in PodeDataDistribution
-- modifications to Weather

-- 0.1.0:	Initial version.
-- Support for (1B) Data Distribution


PODE DEFINITIONS IMPLICIT TAGS::= BEGIN

-- ==============================================
-- P-ODE Messages
-- ==============================================

PodeDataDistribution ::= SEQUENCE {		-- From Data Collector to PODE Core ((1B) Data Distribution))
	dialogID	[0]PodeDialogID,			-- 0x00C0 Data Collector distribution to the ODE core
	seqID		[1]SemiSequenceID,			-- 0x05 Data
	groupID		[2]GroupID,					-- used to group data by source (i.e Municipality)	
	requestID	[3]OCTET STRING (SIZE(4)),	-- used by Collector and Core to manage the data session\connection
	podeData	[4]PodeDataRecord,			-- data record; contains only 1 PodeDataTypes
	messageID	[5]Sha256Hash OPTIONAL		-- Only used for tracing a message from the data source to the emulator; hash of the received byte array from the data source,
}

PodeDataPulicationRegistration::=SEQUENCE {	
	dialogID		[0]PodeDialogID,			-- 0x00C5 PODE Core Data Delivery to subscriber ((1B) Data Pub. Reg)
	seqID			[1]SemiSequenceID,			-- 0x03 Registration Request
	groupID			[2]GroupID,					-- used to group data by source (i.e Municipality, Automotive Manufactures, etc)	
	requestID		[3]OCTET STRING (SIZE(4)),	-- from the ServiceRequest
	source			[4]ServiceProviderID,		-- unique Data Collector identifier; generated by the Data Collector
	regData			[5]PodeDataTypes,			-- data types to be registered
	serviceRegion	[6]GeoRegion OPTIONAL		-- publication geographic region.  If not provided, the geoRegion will be the entire service region of the P-ODE
			-- After successful registration, using PodeDataDistribution, the Data Collector sends PodeDataRecords to the Core as available.
}

PodeSubscriptionRequest::=SEQUENCE {	
	dialogID		[0]PodeDialogID,			-- 0x00C1 (2c) Data Sub Reg-User Subscribes to Core
	seqID			[1]SemiSequenceID,			-- 0x08 subscription request
	groupID			[2]GroupID,					-- used to group data by source (i.e Municipality, Automotive Manufactures, etc.)	
	requestID		[3]OCTET STRING (SIZE(4)),	-- from the ServiceRequest
	type			[4]PodeSubReqType,			-- Subscription Request Type; real-time data vs archive data
	subData			[5]PodeSubData,				-- requested data types
	protocol		[6]PodeProtocol,			-- network protocol in which data should be provided
	endTime			[7]DFullTime,				-- date and time in which the subscription will expire
	serviceRegion	[8]GeoRegion OPTIONAL		-- subscription geographic region.  If not provided, the geoRegion will be the entire service region of the P-ODE
			-- Note: After a Subscription is set up, data matching the subscription is delivered over (1B) Data Delivery using PodeDataDistribution
}

-- (1B) Data Delivery (podeDataDelivery)::= PodeDataDistribution based on PodeSubscriptionRequest

PodeDataDelivery::=SEQUENCE{  
--	dialogID	PodeDialogID,			0x00C1 (1B) Data Delivery; Core delivers data to subscribers
--	seqID		SemiSequenceID,			0x08 subscription request
--	groupID		GroupID,				used to group data by source (i.e Municipality, Automotive Manufactures, etc.)	
--	requestID	OCTET STRING (SIZE(4)),	from the ServiceRequest
	podeData	[0]PodeDataRecord,		-- data record; contains only 1 PodeDataTypes
	messageID	[1]Sha256Hash OPTIONAL 	-- Only used for tracing a message from the data source to the emulator; hash of the received byte array from the data source,
}

PodeLogMessage::= SEQUENCE {	-- Logged data for After Action Review; feasibility Assessment
	dialogID	[0]PodeDialogID,			-- 0x00C4; (1B) Log Message; Logging information from Data Collectors and Emulator to the Core for After Action Review
	seqID		[1]SemiSequenceID,			-- 0x05 (log) Data
	groupID		[2]GroupID,					-- used to group data by source (i.e Municipality)	
	requestID	[3]OCTET STRING (SIZE(4)),	-- 
	dataSource	[4]PodeSource,				-- data source to query for`
	dataType	[5]PodeDataTypes,			-- type of data (PodeDtaRecord) to be logged
	startTime	[6]DDateTime,				-- time the process started
	endTime		[7]DDateTime,				-- time the process ended
	stage		[8]PodeStage,				-- process stage
	msgSize		[9]OCTET STRING (SIZE(4)),	-- size of the message.  Size of the raw message from the source when parsed by the Data Collector.  Size of the ASN.1 encoded message for all other stage log messages
	messageID	[10]Sha256Hash				-- hash of the received byte array from the data source
}

PodeLogDataRequest::= SEQUENCE {		-- query for 0x00C4; (1B) Log Message; Logging information from Data Collectors and Emulator to the Core for After Action Review
	dialogID	[0]PodeDialogID,			-- 0x00C7: (3C) Log Data; Logging information from COre to After Action Review module
	seqID		[1]SemiSequenceID,			-- 0x03: Data Request
	groupID		[2]GroupID,					-- 
	requestID	[3]OCTET STRING (SIZE(4)),	-- 
	query		[4]PodeLogQuery				-- data elements to query for
}

PodeLogDataResponse::= SEQUENCE {
	dialogID	[0]PodeDialogID,			-- 0x00C7: (3C) Log Data; Logging information from COre to After Action Review module
	seqID		[1]SemiSequenceID,			-- 0x05 (requested) Data
	groupID		[2]GroupID,					-- 
	requestID	[3]OCTET STRING (SIZE(4)),	-- 
	logRecords	[4]SEQUENCE (SIZE (1..1000)) OF PodeLogMessage	-- records returned based on PodeLogQuery
}

PodeDataConfirmation ::= SEQUENCE {
	dialogID	[0]PodeDialogID,				-- dependent on dialog
	seqID		[1]SemiSequenceID,				-- 0x04 Data Confirmation
	groupID		[2]GroupID,						-- unique ID used to identify an organization
	requestID	[3]OCTET STRING (SIZE(4)), 		-- from ServiceRequest
	destination	[4]PodeDataDestination OPTIONAL,-- URL the Data Collector should send data to
	hash		[5]Sha256Hash					-- SHA-256 hash of Data
}

-- ************************************************************************
-- need to be flushed out

PodeArchiveData ::= SEQUENCE {	-- Archive interface defined by the RDE, therefore the dialog information not included
--	dialogID	PodeDialogID,			0x00C3; (2C) pode Archive Data; Core archives podeDataDeposit to RDE
--	seqID		SemiSequenceID,			 
--	groupID		GroupID,				used to group data by source (i.e Municipality)	
--	requestID	OCTET STRING (SIZE(4)),	 
	dateStamp	[0]DDateTime,		-- current date and time stamp to the ms (time in which PodeDtaRecord is sent to the RDE)
	dataType	[1]PodeDataTypes,	-- type of data contained in PodeDtaRecord
	geoRegion	[2]GeoRegion,		-- geographic region of the PodeDataRecord being archived.
										-- For PodeWeatherinfo geoRegion is Position3D
										-- For PodeDetectorData geoRegion is Position3D
										-- For PodeSpatMap geoRegion is the Reference Point in the Map
	podeData	[3]OCTET STRING			-- PodeDataRecord to be archived
}

PodeAchriveDataRequest ::= SEQUENCE {  -- Retrieve interface defined by the RDE, therefore the dialog information not included
--	dialogID	PodeDialogID,			0x00C6(3C) Data Archive Retrieval from the RDE
--	seqID		SemiSequenceID,			 
--	groupID		GroupID,				 
--	requestID	OCTET STRING (SIZE(4))	 
	dateRange	[0]PodeReplayData,		-- Start and End Date and Time Stamp for data to be retrieved
	dataType	[1]PodeDataTypes,		-- type of data (PodeDtaRecord) to be retrieved
	geoRegion	[2]GeoRegion OPTIONAL	-- geographic region of the requested data.  If not provided, all available data will be provided
}

PodeArchiveDataDistribution::= SEQUENCE { -- Retrieve interface defined by the RDE, therefore the dialog information not included
--	dialogID	PodeDialogID,			0x00C6; ((3C) Data Archive Retrieval from the RDE
--	seqID		SemiSequenceID,			 
--	groupID		GroupID,				used to group data by source (i.e Municipality)	
--	requestID	OCTET STRING (SIZE(4)),	 
	dateStamp	[0]DDateTime,		-- IS THIS REALLY REQUIRED? date and time stamp to the ms when the data was archived
	dataType	[1]PodeDataTypes,	-- IS THIS REALLY REQUIRED? type of data contained in PodeDtaRecord
	podeData	[2]OCTET STRING		-- PodeDataRecord distributed to the Core for delivery to subscriber
}

-- ************************************************************************

-- ==============================================
-- P-ODE Data Frames
-- ==============================================

PodeDataRecord ::= SEQUENCE {
	source			[0]PodeSource,					-- data source; P-ODE Data Collector
	lastupdatetime	[1]DDateTime,		 			-- if not provided by source, then system time when received by Data Collector
	measduration	[2]INTEGER (1..60) OPTIONAL,	-- in units of minutes
	routename		[3]UTF8String OPTIONAL,			-- Descriptive Route\street Name
	podeData		[4]CHOICE {
						weather		[0]PodeWeatherinfo,		-- weather data
						detector	[1]PodeDetectorData,	-- vehicle\traffic detector data
						spatMap		[2]PodeSpatMap			-- SPaT and Map Data
				}
}

PodeDetectorData::= SEQUENCE {
	detectorID		[0]UTF8String,
	stationID		[1]UTF8String OPTIONAL,
	detectMethod	[2]PodeDetectionMethod OPTIONAL,
	status			[3]PodeDetectorStatus OPTIONAL,	
	position		[4]Position3D OPTIONAL, 				-- location of detector\sensor
	mileMarker		[5]OCTET STRING (SIZE(1)) OPTIONAL,	-- reported value*10, converted to Hex
	laneData		[6]SEQUENCE (SIZE (1..10)) OF PodeLaneData
}

PodeWeatherinfo::= SEQUENCE {
	sourceID			[0]OCTET STRING (SIZE(4)),
	obsTypeID			[1]OCTET STRING (SIZE(4)),
	sensorID			[2]OCTET STRING (SIZE(4)),
	sensorIndex			[3]INTEGER (0..60),
	platformID			[4]OCTET STRING (SIZE(4)),
	siteID				[5]OCTET STRING (SIZE(4)),
	category			[6]PodeCategory,
	contribID			[7]OCTET STRING (SIZE(4)),
	contributor			[8]UTF8String,		-- text
	platformCode		[9]UTF8String,		-- text
	position			[10]Position3D,
	weatherSenorData	[11]PodeWeatherData
}

PodeWeatherData::= SEQUENCE {
	airTemp					[0]AmbientAirTemperature OPTIONAL,
	airPress				[1]AmbientAirPressure OPTIONAL,
	dewPointTemp			[2]AmbientAirTemperature OPTIONAL,
	maxTemp					[3]AmbientAirTemperature OPTIONAL,
	minTemp					[4]AmbientAirTemperature OPTIONAL,	
	relativeHumidty			[5]Percentage OPTIONAL,
	precipYesNo				[6]PrecipYesNo OPTIONAL,
	precipSit				[7]PrecipSituation OPTIONAL,
	precipRate				[8]PrecipRate OPTIONAL,
	visibility				[9]Distance OPTIONAL,
	visibilitySituation		[10]VisibilitySituation OPTIONAL,
	mobileFriction			[11]Percentage OPTIONAL,
	surfaceStatus			[12]SurfaceStatus OPTIONAL,
	surfaceTemperature		[13]AmbientAirTemperature OPTIONAL,
	pavementTemperature		[14]AmbientAirTemperature OPTIONAL,
	windSenAvSpeed			[15]Speed OPTIONAL,
	windSenAvDirection		[16]Heading OPTIONAL,
	surfaceFreezePoint		[17]AmbientAirTemperature OPTIONAL,
	surfaceBlackIceSignal	[18]SurfaceBlackIceSignal OPTIONAL
	-- Additional Weather Data
}

PodeLaneData::= SEQUENCE {
	lane	[0]PodeLaneInfo,
	data	[1]PodeDataElementList
}

PodeLaneInfo ::= SEQUENCE {
	zoneNum			[0]INTEGER (0..99999),		-- "0" indicates "unknown", VDOT nodeid, RITIS zone-number, BluFax bnid
	laneDirection 	[1]PodeLaneDirection,
	laneType 		[2]PodeLaneType OPTIONAL,
	laneNumber		[3]INTEGER (1..25) OPTIONAL
}

PodeDataElementList ::= SEQUENCE {
	speed			[0]Speed OPTIONAL,				-- SAE J2735 Speed.   INTEGER (0..8191).  The value 8191 indicates that speed is unavailable.  Represents vehicle speed expressed in unsigned units of 0.02 meters per second.
	occupancy		[1]INTEGER (1..100) OPTIONAL,	-- The percentage of time a vehicle is in sensor range
	volume			[2]INTEGER (1..25) OPTIONAL,	-- number of vehicles for the given measureduration
	travelTimeInfo	[3]PodeTravelTime OPTIONAL
}

PodeTravelTime ::= SEQUENCE {
	travelTime			[1]DMinute,
	travelTimeAlgorithm	[2]PodeTravelTimeAlgorithm OPTIONAL,
	travelTimeScore		[3]INTEGER (1..100) OPTIONAL,
	travelTimeType		[4]PodeTravelTimeType OPTIONAL,
	travelTimeDelayInfo	[5]PodeTravelTimeDelayInfo OPTIONAL
}

PodeTravelTimeDelayInfo::=SEQUENCE {
	delay			[0]INTEGER (1..500), 			-- in seconds
	linkDelay		[1]INTEGER (1..500) OPTIONAL,	-- in seconds
	routeDelay		[2]INTEGER (1..500) OPTIONAL,	-- in seconds
	prediction		[3]PodeTravelTimeRoutePrediction OPTIONAL
}

PodeSubData::=SEQUENCE {
	dataElements	[0]PodeDataTypes,				-- list a data elements requested
	laneDirect 		[1]PodeLaneDirection OPTIONAL, -- limit subscription to a specific direction, if not included, all directions are provided
	laneType		[2]PodeLaneType OPTIONAL	 	-- limit subscription to a specific lane type, if not included, all lane types are provided
}

PodeSpatMap::=SEQUENCE {
	fhwaSpat	[0]OCTET STRING (SIZE(1400)),	-- FHWA SPaT message BLOB.  See J2735_SPATblob_MAPblob_ RevC_20120217.doc for message definition
	fhwaMap		[1]OCTET STRING (SIZE(1400))	-- FHWA Map message BLOB.  See J2735_SPATblob_MAPblob_ RevC_20120217.doc for message definition
	--position	[2]Position3D					 Intersection location
}

PodeSubReqType ::= CHOICE {
	realTimeData	[0]PodeRealTimeData,	-- data is distributed in near "real-time" as it arrives at the P-ODE Core
	replayData		[1]PodeReplayData	-- data archived in the RDE is distributed to subscribers in a simulated "real time" manor
	 --Additional PodeSubReqType
}

PodeReplayData::= SEQUENCE{
	startTime	[0]DFullTime,			-- Date and Time from which the replay should start
	endTIme		[1]DFullTime OPTIONAL	-- Date and Time from which the replay should End.  if not included, all data between startTime and current time will be replayed
}

PodeLogQuery::= SEQUENCE{
	startTime	[0]DDateTime,						-- date & time in which to start the query from
	endTime		[1]DDateTime OPTIONAL,				-- date & time in which to end the query
	requestID	[2]OCTET STRING (SIZE(4)) OPTIONAL,	--requestID to query for
	groupID		[3]OCTET STRING (SIZE(4)) OPTIONAL,	--groupID to query for
	stage		[4]PodeStage OPTIONAL,				-- process stage to query for
--	exception	PodeExecption OPTIONAL,				exception to query for
	dataType	[5]PodeDataTypes  OPTIONAL,			-- data type to query for
	dataSource	[6]PodeSource  OPTIONAL,			-- data source to query for`
	messageID	[7]Sha256Hash  OPTIONAL				-- hash of the received byte array
}

PodeDataDestination::=SEQUENCE {
	speedURL		[0]IA5String (SIZE(1..150)) OPTIONAL,	-- URL to send speed data
	volumeURL		[1]IA5String (SIZE(1..150)) OPTIONAL,	-- URL to send volume data
	occupancyURL	[2]IA5String (SIZE(1..150)) OPTIONAL,	-- URL to send occupancy data
	travelTimeURL	[3]IA5String (SIZE(1..150)) OPTIONAL,	-- URL to send Travel Time data
	weatherURL		[4]IA5String (SIZE(1..150)) OPTIONAL	-- URL to send Weather data
}

-- ==============================================
-- P-ODE Data Elements
-- ==============================================

PodeSource ::= ENUMERATED {	
	reserved	(0),
	vdot    	(1), 	--first Byte of requestID = 0x1000
	ritis   	(2), 	--first Byte of requestID = 0x2000
	blufax		(3),	--first Byte of requestID = 0x3000
	dms     	(4),	--first Byte of requestID = 0x4000
	rtms    	(5),	--first Byte of requestID = 0x5000
	spat		(6), 	--first Byte of requestID = 0x6000
	wxde		(7)	--first Byte of requestID = 0x7000
	  -- Additional Data Sources
	-- consider adding application sources for After Action Review ((1B) Log Message) purposes
}

PodeLaneType::= ENUMERATED {
	unknown		(0),
	offRamp		(1),
	onRamp		(2),
	normal		(3),
	shoulder	(4)
	 -- additional laneType
}

PodeLaneDirection::= ENUMERATED {
	unknown		(0),
	north		(1),	-- 337.6-22.5 Degrees 
	northEast	(2),	-- 22.6-67.5 Degrees 
	east 		(3),	-- 67.6-112.5 Degrees
	southEast 	(4),	-- 112.6-157.5 Degrees
	south 		(5),	-- 157.6-202.5 Degrees
	southWest 	(6),	-- 202.6-247.5 Degrees
	west		(7),	-- 247.6-292.5 Degrees
	northWest 	(8)		-- 292.6-337.5 Degrees

	-- Heading in degrees to Directional Text descriptions (primarily for BSMs)
		-- Degrees			Directional descriptions
		-- 337.6-22.5 	=	north
		-- 22.6-67.5	=	northeast
		-- 67.6-112.5	=	east
		-- 112.6-157.5	=	southeast
		-- 157.6-202.5	=	south
		-- 202.6-247.5	=	southwest
		-- 247.6-292.5	=	west
		-- 292.6-337.5	=	northwest
}

PodeStage::= ENUMERATED {
	reserved	(0),
	parse		(1),
	sanitize	(2),
	encrypt		(3),
	send		(4),
	received	(5),
	unknown		(6)
	 -- Additional Stages	
}

PodeDetectionMethod::= ENUMERATED {
	unknown			(0),
	vehicleProbe	(1)
	 -- Additional Detection Methods
}

PodeDetectorStatus::= ENUMERATED {
	unknown			(0),
	noDetermination	(1)
	 -- Additional Status indications	
}

PodeTravelTimeAlgorithm::= ENUMERATED {
	unknown	(0),
	actual	(1)
	 -- Additional Algorithms
}

PodeTravelTimeType::=  ENUMERATED {
	unknown	(0),
	actual	(1)
	 -- Additional TravelTimeTypes
}

PodeTravelTimeRoutePrediction::=  ENUMERATED {
	no	(0),
	yes	(1)
	 -- Additional Predictions
}

PodeDialogID::= ENUMERATED {
	podeDataDistribution			(192),	-- 0x00C0 (1B) Data Distribution; Data Collector data distribution to the PODE Data Core
	podeDataSubscriptionRegistration(193),	-- 0x00C1 (2C) Data Sub Reg(user subscribes to data from the Core)
	podeDataDelivery				(194),	-- 0x00C2 (1B) Data Delivery 
	podeArchiveData					(195),	-- 0x00C3 (2C) PODE Archive Data: Core archives Data to Reach Data Exchange
	podeLogMessage					(196),	-- 0x00C4 (1B) Log Message: Logging information from Data Collectors and Emulator to the Core for After Action Review and analysis
	podeDataPulicationRegistration	(197),	-- 0x00C5 (1B) Data Pub Reg (Data Collector Data Publication Registration); Data Collectors register available data with the Core
	podeDataArchiveRetrival			(198),	-- 0x00C6 (3C) Data Archive Retrieval; Core requests data from RDE
	podeLogData						(199)	-- 0x00C7 (3C) log Data: After Action Review query for (1B) log Message data
	 -- additional DialogIDs
}

PodeDataTypes::= OCTET STRING (SIZE(1))
	-- reserved		(0),
	-- speed		(1),	"00000001"  if PodeDataRecord\podeData\PodeDetectorData\PodeLaneData\PodeDataElementList\speed
	-- occupancy	(2),	"00000010"  if PodeDataRecord\podeData\PodeDetectorData\PodeLaneData\PodeDataElementList\occupancy
	-- volume		(4),	"00000100"  if PodeDataRecord\podeData\PodeDetectorData\PodeLaneData\PodeDataElementList\volume
	-- travelTime	(8),	"00001000"  if PodeDataRecord\podeData\PodeDetectorData\PodeLaneData\PodeDataElementList\travelTime
	-- weather		(16),	"00010000"  if PodeDataRecord\podeData\PodeWeatherinfo
	-- raw			(32),	"00100000"
	-- spatMap		(64)    "01000000"  if PodeDataRecord\podeData\PodeSpatMap
	-- any combination of defined data elements can be selected, i.e. all data elements would be "00011111"

PrecipYesNo::= ENUMERATED {
	precip 		(1),	-- from NTCIP 1204 version v02
	noPrecip	(2),
	error 		(3)
}

PrecipSituation::= ENUMERATED {
	other 						(1),	-- from NTCIP 1204 version v02
	unknown 					(2),
	noPrecipitation 			(3),
	unidentifiedSlight 			(4),
	unidentifiedModerate 		(5),
	unidentifiedHeavy 			(6),
	snowSlight 					(7),
	snowModerate 				(8),
	snowHeavy 					(9),
	rainSlight 					(10),
	rainModerate 				(11),
	rainHeavy 					(12),
	frozenPrecipitationSlight 	(13),
	frozenPrecipitationModerate	(14),
	frozenPrecipitationHeavy 	(15)
}

VisibilitySituation::= ENUMERATED {
	other 				(1),	-- from NTCIP 1204 version v02
	unknown 			(2),
	clear 				(3),
	fogNotPatchy 		(4),
	patchyFog 			(5),
	blowingSnow 		(6),
	smoke 				(7),
	seaSpray 			(8),
	vehicleSpray 		(9),
	blowingDustOrSand	(10),
	sunGlare 			(11),
	swarmsOfInsects 	(12)
}

SurfaceStatus::= ENUMERATED {
	other 					(1),	-- from NTCIP 1204 version v02
	error 					(2),
	dry 					(3),
	traceMoisture 			(4),
	wet 					(5),
	chemicallyWet 			(6),
	iceWarning 				(7),
	iceWatch 				(8),
	snowWarning 			(9),
	snowWatch 				(10),
	absorption 				(11),
	dew 					(12),
	frost 					(13),
	absorptionAtDewpoint	(14)
}

SurfaceBlackIceSignal::= ENUMERATED {
	other 			(1),	-- from NTCIP 1204 version v02
	noIce 			(2),
	blackIce 		(3),
	detectorError	(4)
}

Distance ::= OCTET STRING (SIZE(2))
	-- range from 0 to 10000m
	-- unknown = 0xF000

PrecipRate ::= INTEGER (0..255)
	--  Range of 0 to 15.24 cm\h with a resolution of 0.06 cm
	-- 250 (dec)(0xFA) is a PrecipRate of 15 cm/h
	-- 255 (dec)(0xFF) = "unknown"

Percentage ::= INTEGER (0..200)
-- LSB units of 0.5 percent

GroupID ::= OCTET STRING (SIZE(4))
	-- GroupID definition
	-- VDOT GroupID begins with 0x1000
	-- RITIS GroupID begins with 0x2000
	-- BluFax GroupID begins with 0x3000
	-- DMS GroupID begins with 0x4000
	-- RTMS GroupID begins with 0x5000
	-- SPaT GroupID begins with 0x6000	

PodeCategory::= ENUMERATED {
	reserved	(0),
	t 			(1),
	p 			(2)
}

PodeRealTimeData::= OCTET STRING (SIZE(1))
	--	realTimeData	(1)		"00000001"

	
PodeExecption::=  ENUMERATED {
	reserved		(0),
	badDataFormat 	(1),
	fieldOutOfRange	(2),
	sessionTimeOut	(3)
	 --other exceptions
}

PodeProtocol::=  ENUMERATED {
	reserved		(0),
	upd			 	(1),
	tcp				(2)
		 --other exceptions
}

-- ====================
-- P-ODE objects that NEED TO BE DEVELOEPD FURTHER
-- ====================
-- Temp
		-- airTemp
		-- dewPointTemp
		-- maxTemp
		-- minTemp

--airPress
--relativeHumidty

-- presip:
	-- precipYesNo
	-- precipSit
	-- precipRate

-- visibility:
	-- visibility
	-- visibilitySituation

-- mobileFriction


-- wind:
	-- windSenAvSpeed
	-- windSenAvDirection

-- Surface:
	-- surfaceStatus
	-- surfaceTemperature
	-- pavementTemperature
	-- surfaceFreezePoint
	-- surfaceBlackIceSignal



-- ==============================================
-- SEMI Definitions
-- ==============================================	

ServiceRequest ::= SEQUENCE {
	dialogID	[0]PodeDialogID,				-- dependent on dialog
	seqID		[1]SemiSequenceID,				-- 0x01 Service Request
	groupID		[2]GroupID,					-- unique ID used to identify an organization that this service should be associated with
	requestID	[3]OCTET STRING (SIZE(4)),		-- random 4 byte ID generated for trust establishment
	destination	[4]ConnectionPoint	OPTIONAL	-- the local IP and port that the remote system will send data to
}

ServiceResponse ::= SEQUENCE {
	dialogID		[0]PodeDialogID,			-- dependent on dialog
	seqID			[1]SemiSequenceID,			-- 0x02 Service Response
	groupID			[2]GroupID,				-- matches groupID in ServiceRequest
	requestID		[3]OCTET STRING (SIZE(4)), -- matches requestID in ServiceRequest
	expiration		[4]DDateTime, 				-- 
	serviceRegion	[5]GeoRegion OPTIONAL,		-- the region applicable for this service
	hash			[6]Sha256Hash				-- SHA-256 hash of ServiceRequest
}

DataSubscriptionResponse ::= SEQUENCE {
	dialogID	[0]PodeDialogID,				-- 0x00C1 (2C) Data Sub Reg(user subscribes to data from the Core)
	seqID		[1]SemiSequenceID,				-- 0x09 Subscription Response
	groupID		[2]GroupID,					-- unique ID used to identify an organization
	requestID	[3]OCTET STRING (SIZE(4)),			-- matches requestID in DataSubscriptionRequest
	subID		[4]OCTET STRING (SIZE(4)), 			-- random 4 byte ID generated for this subscription
	err			[5]INTEGER (0..65535) OPTIONAL	-- Error Code if SubscriptionRequest 
											-- fails (16 unsigned bits)
}

DataSubscriptionCancel ::= SEQUENCE {
	dialogID	[0]PodeDialogID,				-- 0x00C1 (2C) Data Sub Reg(user subscribes to data from the Core)
	seqID		[1]SemiSequenceID,				-- 0x0A Subscription Request
	groupID		[2]GroupID,					-- unique ID used to identify an organization
	requestID	[3]OCTET STRING (SIZE(4)),		-- matches requestID in DataSubscriptionRequest
	subID		[4]OCTET STRING (SIZE(4))		-- matches subID in DataSubscriptionResponse
}

SemiSequenceID::= ENUMERATED {
	svcReq				(1),	-- Service request
	svcResp				(2),	-- Service response
	dataReq				(3),	-- Data request
	dataConf			(4),	-- Data confirmation
	data				(5),	-- Data 
	accept				(6),	-- Acceptance
	receipt				(7),	-- Receipt
	subscriptionReq		(8),	-- Subscription Request
	subscriptinoResp	(9),	-- Subscription Response
	subscriptionCancel	(10)	-- Subscription Cancellation
	 -- additional SeqIDs
}

GeoRegion::= SEQUENCE {
	nwCorner	[0]Position3D,		-- Northwest corner
	seCorner	[1]Position3D		-- Southeast corner
}

ConnectionPoint ::= SEQUENCE {
	address	[0]IpAddress	OPTIONAL,
	port	[1]PortNumber
}

IpAddress ::= CHOICE {
	ipv4Address	[0]IPv4Address,
	ipv6Address	[1]IPv6Address
}

ServiceProviderID ::= OCTET STRING(SIZE(4))

Sha256Hash ::=	OCTET STRING (SIZE(64))	
	
IPv4Address ::= OCTET STRING(SIZE(4))

IPv6Address ::= OCTET STRING(SIZE(16))

PortNumber ::= INTEGER(0..65535)

-- ==============================================
-- J2735 Definitions
-- ==============================================
	
DDateTime ::= SEQUENCE {
	year	[0]DYear OPTIONAL, 		-- 2 bytes
	month 	[1]DMonth OPTIONAL,		-- 1 byte
	day 	[2]DDay OPTIONAL, 		-- 1 byte
	hour 	[3]DHour OPTIONAL, 		-- 1 byte
	minute 	[4]DMinute OPTIONAL,	-- 1 byte
	second 	[5]DSecond OPTIONAL 	-- 2 bytes
}

DFullTime ::= SEQUENCE {
	year	[0]DYear OPTIONAL, 	-- 2 bytes
	month 	[1]DMonth OPTIONAL, -- 1 byte
	day 	[2]DDay OPTIONAL, 	-- 1 byte
	hour 	[3]DHour OPTIONAL, 	-- 1 byte
	minute 	[4]DMinute OPTIONAL	-- 1 byte
}


Position3D ::= SEQUENCE {
	lat 		[0]Latitude,	-- in 1/10th micro degrees
	lon 		[1]Longitude,	-- in 1/10th micro degrees
	elevation	[2]Elevation OPTIONAL
}

Latitude ::= INTEGER (-900000000..900000001)
	-- LSB = 1/10 micro degree
	-- Providing a range of plus-minus 90 degrees

Longitude ::= INTEGER (-1800000000..1800000001)
	-- LSB = 1/10 micro degree
	-- Providing a range of plus-minus 180 degrees

Elevation ::= OCTET STRING (SIZE(2))
	-- 1 decimeter LSB (10 cm)
	-- Encode elevations from 0 to 6143.9 meters
	-- above the reference ellipsoid as 0x0000 to 0xEFFF.
	-- Encode elevations from -409.5 to -0.1 meters,
	-- i.e. below the reference ellipsoid, as 0xF001 to 0xFFFF
	-- unknown as 0xF000

DYear ::= INTEGER (0..9999) -- units of years

DMonth ::= INTEGER (0..15) -- units of months	
	-- Integer values from one to 12 representing the month within a year.
	-- The range 13 to 14 and the value zero are all reserved.
	-- The value of 15 SHALL represent an unknown value.

DDay ::= INTEGER (0..31) -- units of days

DHour ::= INTEGER (0..31) -- units of hours
	-- Integer values from zero to 23 representing the hours within a day
	-- The range 24 to 30 is reserved.
	-- The value of 31 SHALL represent an unknown value

DMinute ::= INTEGER (0..63) -- units of minutes
	-- integer values from zero to 59 representing the minutes within an hour.
	-- The range 60 to 62 is reserved.
	-- The value of 63 SHALL represent an unknown value,

DSecond ::= INTEGER (0..65535) -- units of miliseconds
	-- integer values from zero to 60999 representing the milliseconds within a minute.
	-- A leap second is represented by the value range 60001 to 60999.
	-- The value of 65535 SHALL represent an unavailable value in the range of the minute, other values from 61000 to 65534 are reserved.
	
AmbientAirPressure ::= INTEGER (0..255)
	-- from J2735
	-- 8 Bits in hPa starting at 580 with a resolution of 2 hPa resulting in a range of 580 to 1090"
	-- 1 hPa = 1 mbar

AmbientAirTemperature ::= INTEGER (0..191)
	-- from J2735
	-- in deg C with a -40 offset
	-- This provides for a precision of one degree centigrade and a range of -40 to +150 degrees
	-- encoded in a one byte value. The value of -40 deg C is encoded as zero and every degree 
	-- above that increments the transmitted value by one resulting in a transmission range of 0 to 191"
	
Heading ::= INTEGER (0..28800)
	-- from J2735
	-- LSB of 0.0125 degrees (<decimal value>*.0125=direction in degrees, 0= due North (WSG-84), 28800 (360)="unknown" direction)
	-- A range of 0 to 359.9875 degrees		
	
Speed ::= INTEGER (0..8191)
	-- from J2735
	-- Units of 0.02 m/s


END
-- END of PODE module
